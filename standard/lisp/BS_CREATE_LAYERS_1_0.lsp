; BS CAD Standard 1.0 - Core layer creation script
; Command: BS_CREATE_LAYERS_1_0
; Encoding: UTF-8 with BOM

(vl-load-com)

(defun bs:vla-bool (value)
  (if value :vlax-true :vlax-false)
)

(defun bs:load-linetype (name / doc)
  (setq doc (vla-get-ActiveDocument (vlax-get-acad-object)))
  (if (not (tblsearch "LTYPE" name))
    (vl-catch-all-apply 'vla-Load (list (vla-get-Linetypes doc) name "acad.lin"))
  )
)

(defun bs:ensure-layer (item / doc layers layer-name color ltype lw trans plot desc layer)
  (setq doc (vla-get-ActiveDocument (vlax-get-acad-object)))
  (setq layers (vla-get-Layers doc))
  (setq layer-name (nth 0 item))
  (setq color (nth 1 item))
  (setq ltype (nth 2 item))
  (setq lw (nth 3 item))
  (setq trans (nth 4 item))
  (setq plot (nth 5 item))
  (setq desc (nth 6 item))
  (if (tblsearch "LAYER" layer-name)
    (setq layer (vla-Item layers layer-name))
    (setq layer (vla-Add layers layer-name))
  )
  (vla-put-Color layer color)
  (if (tblsearch "LTYPE" ltype) (vla-put-Linetype layer ltype))
  (vl-catch-all-apply 'vla-put-Lineweight (list layer lw))
  (vl-catch-all-apply 'vla-put-Plottable (list layer (bs:vla-bool plot)))
  (if (> trans 0) (vl-catch-all-apply 'vla-put-Transparency (list layer trans)))
  (if (> (strlen desc) 0) (vl-catch-all-apply 'vla-put-Description (list layer desc)))
)

(defun c:BS_CREATE_LAYERS_1_0 (/ layer-data item)
  (foreach lt '("Continuous" "Hidden" "Dashed" "Center")
    (bs:load-linetype lt)
  )
  (setq layer-data
    '(
    ("01-AR-原有墙体" 253 "Continuous" 25 0 T "原有墙体")
    ("01-AR-墙体" 7 "Continuous" 35 0 T "墙体")
    ("01-AR-墙体填充" 250 "Continuous" 9 0 T "墙体填充")
    ("01-AR-拆除墙体" 1 "Dashed" 25 0 T "拆除墙体")
    ("01-AR-新建墙体" 1 "Continuous" 40 0 T "新建墙体")
    ("01-AR-柱" 7 "Continuous" 40 0 T "柱")
    ("01-AR-洞口" 140 "Continuous" 18 0 T "洞口")
    ("01-AR-窗" 4 "Continuous" 18 0 T "窗")
    ("01-AR-窗-开启" 8 "Dashed" 9 0 T "窗开启线")
    ("01-AR-门" 3 "Continuous" 18 0 T "门")
    ("01-AR-门-开启" 8 "Dashed" 9 0 T "门开启线")
    ("02-IN-LOGO墙" 6 "Continuous" 18 0 T "LOGO墙")
    ("02-IN-完成面" 9 "Continuous" 18 0 T "完成面")
    ("02-IN-完成面填充" 252 "Continuous" 9 0 T "完成面填充")
    ("02-IN-导视标识" 200 "Continuous" 18 0 T "导视标识")
    ("02-IN-玻璃" 151 "Continuous" 18 0 T "玻璃")
    ("02-IN-装饰造型" 30 "Continuous" 18 0 T "装饰造型")
    ("02-IN-踢脚线" 250 "Continuous" 13 0 T "踢脚线")
    ("03-FL-地面" 34 "Continuous" 18 0 T "地面轮廓")
    ("03-FL-地面填充" 253 "Continuous" 9 0 T "地面填充")
    ("03-FL-地面拼花" 8 "Continuous" 13 0 T "地面拼花/分缝")
    ("03-FL-地面材质" 251 "Continuous" 13 0 T "地面材质")
    ("03-FL-地面高差" 1 "Continuous" 18 0 T "地面高差")
    ("04-CE-吊顶" 140 "Continuous" 18 0 T "吊顶轮廓")
    ("04-CE-吊顶-隐藏线" 8 "Hidden" 9 0 T "吊顶隐藏线")
    ("04-CE-吊顶填充" 253 "Continuous" 9 0 T "吊顶填充")
    ("04-CE-吊顶标高" 6 "Continuous" 18 0 T "吊顶标高")
    ("04-CE-天花分格" 151 "Continuous" 13 0 T "天花分格")
    ("04-CE-检修口" 8 "Continuous" 13 0 T "检修口")
    ("04-CE-灯槽" 30 "Continuous" 18 0 T "灯槽")
    ("05-FU-层架" 44 "Continuous" 18 0 T "层架/货架")
    ("05-FU-展柜" 2 "Continuous" 18 0 T "展柜")
    ("05-FU-展柜-内部分隔" 8 "Continuous" 9 0 T "展柜内部分隔")
    ("05-FU-展柜-开启" 8 "Dashed" 9 0 T "展柜开启线")
    ("05-FU-展示台" 30 "Continuous" 18 0 T "展示台")
    ("05-FU-工位" 46 "Continuous" 18 0 T "工位")
    ("05-FU-接待台" 41 "Continuous" 18 0 T "接待台/前台")
    ("05-FU-柜体" 40 "Continuous" 18 0 T "柜体")
    ("05-FU-柜体-内部分隔" 8 "Continuous" 9 0 T "柜体内部分隔")
    ("05-FU-柜体-开启" 8 "Dashed" 9 0 T "柜体开启线")
    ("05-FU-桌椅" 43 "Continuous" 18 0 T "桌椅")
    ("06-EX-LOGO" 6 "Continuous" 18 0 T "LOGO/品牌标识")
    ("06-EX-展板" 200 "Continuous" 18 0 T "展板")
    ("06-EX-展陈内容" 202 "Continuous" 18 0 T "展陈内容")
    ("06-EX-显示屏" 5 "Continuous" 18 0 T "展厅显示屏")
    ("06-EX-灯箱" 30 "Continuous" 18 0 T "灯箱")
    ("06-EX-画面" 201 "Continuous" 18 0 T "画面/喷绘/图文")
    ("07-LI-射灯" 40 "Continuous" 13 0 T "射灯")
    ("07-LI-灯具-辅助线" 8 "Dashed" 9 0 nil "灯具辅助线")
    ("07-LI-灯带" 2 "Continuous" 13 0 T "灯带/线性灯")
    ("07-LI-筒灯" 142 "Continuous" 13 0 T "筒灯")
    ("07-LI-轨道灯" 50 "Continuous" 13 0 T "轨道灯")
    ("08-EL-地插" 92 "Continuous" 18 0 T "地插")
    ("08-EL-开关" 3 "Continuous" 18 0 T "开关")
    ("08-EL-强电线路" 82 "Continuous" 13 0 T "强电线路")
    ("08-EL-插座" 94 "Continuous" 18 0 T "插座")
    ("08-EL-设备电源点" 90 "Continuous" 18 0 T "设备电源点")
    ("09-WK-弱电线路" 136 "Continuous" 13 0 T "弱电线路")
    ("09-WK-显示屏" 5 "Continuous" 18 0 T "显示屏")
    ("09-WK-监控" 132 "Continuous" 18 0 T "监控摄像头")
    ("09-WK-网络点" 130 "Continuous" 18 0 T "网络点")
    ("09-WK-音响点位" 134 "Continuous" 18 0 T "音响点位")
    ("10-EQ-检修口" 8 "Continuous" 18 0 T "设备检修口")
    ("10-EQ-空调设备" 151 "Continuous" 18 0 T "空调设备")
    ("10-EQ-通用设备" 250 "Continuous" 18 0 T "通用设备")
    ("10-EQ-风口" 140 "Continuous" 18 0 T "风口")
    ("11-FI-喷淋" 1 "Continuous" 18 0 T "喷淋")
    ("11-FI-烟感" 10 "Continuous" 18 0 T "烟感")
    ("11-FI-疏散指示" 20 "Continuous" 18 0 T "疏散指示")
    ("12-PL-排水" 150 "Continuous" 18 0 T "排水")
    ("12-PL-给水" 5 "Continuous" 18 0 T "给水")
    ("13-TX-普通文字" 7 "Continuous" 18 0 T "普通文字")
    ("13-TX-标题文字" 6 "Continuous" 25 0 T "标题文字")
    ("13-TX-说明文字" 3 "Continuous" 18 0 T "说明文字")
    ("14-DM-尺寸标注" 6 "Continuous" 18 0 T "尺寸标注")
    ("14-DM-引线标注" 201 "Continuous" 18 0 T "引线标注")
    ("14-DM-标高" 200 "Continuous" 18 0 T "标高")
    ("14-DM-符号" 202 "Continuous" 18 0 T "符号")
    ("15-FR-图框" 7 "Continuous" 50 0 T "图框")
    ("15-FR-标题栏" 7 "Continuous" 25 0 T "标题栏")
    ("15-FR-视口" 8 "Continuous" 9 0 T "视口")
    ("16-RF-原始底图" 253 "Continuous" 9 50 T "原始底图")
    ("16-RF-外部参照" 253 "Continuous" 9 50 T "外部参照")
    ("17-AN-不打印线" 8 "Continuous" 9 0 nil "不打印线")
    ("17-AN-中心线" 8 "Center" 9 0 nil "中心线")
    ("17-AN-临时对象" 250 "Continuous" 9 0 nil "临时对象")
    ("17-AN-辅助填充" 250 "Continuous" 9 50 nil "辅助填充")
    ("17-AN-辅助线" 8 "Continuous" 9 0 nil "辅助线")
    )
  )
  (foreach item layer-data (bs:ensure-layer item))
  (princ (strcat "\nBS CAD Standard 1.0: created/updated " (itoa (length layer-data)) " core layers."))
  (princ)
)

(princ "\nCommand loaded: BS_CREATE_LAYERS_1_0")
(princ)
